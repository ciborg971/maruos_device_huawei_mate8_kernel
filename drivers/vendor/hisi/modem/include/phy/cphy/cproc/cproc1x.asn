--/*********************************************************************************/
--/* FileName:      cproc1x.asn                                                    */
--/* Description:   H2ASN TOOLS Generate ASN.1 file                                */
--/* CopyRight:     Huawei Technologies Co., Ltd.                                  */
--/* Created By:                                                                   */
--/* HISTORY VER:   NULL                                                           */
--/* VERSION:       1.0                                                            */
--/* Create Time:   2015.2.28 10:23:13                                             */
--/* Create Option: H2ASN cproc1x.h cproc1x.asn                                    */
--/*********************************************************************************/
                                                                                   
--ROOT    : Cproc1x-definitions.Cproc1x-MSG                                              
--PROTOCOL: Cproc1x                                                                     
--ENDIAN  : LITTLE                                                                   
--BOUNDARY: ALIGN                                                                    
--THREAD  : MULTI                                                                    
                                                                                     
Cproc1x-definitions DEFINITIONS ::=                                                             
BEGIN                                                                                
                                                                                   
VOS-UINT8  ::= <V,V|LEN-8>INTEGER(0..255) 

VOS-UINT16 ::= <V,V|LEN-16>INTEGER(0..65535) 

VOS-UINT32 ::= <V,V|LEN-32>INTEGER(0..4294967295) 

VOS-RATMODE-ENUM    ::= <V,V|LEN-32> ENUMERATED  
{ 
    vOS-RATMODE-GSM(0), 
    vOS-RATMODE-WCDMA(1), 
    vOS-RATMODE-LTE(2), 
    vOS-RATMODE-TDS(3), 
    vOS-RATMODE-1X(4), 
    vOS-RATMODE-EVDO(5), 
    vOS-RATMODE-BUTT(6) 
} 

MODEM-ID-ENUM    ::= <V,V|LEN-16> ENUMERATED  
{ 
    mODEM-ID-BUTT(0) 
} 

MsgBlock    ::= <V> SEQUENCE  
{ 
     
    dummy    <V>SEQUENCE(SIZE(4)) OF VOS-UINT8 
} 

CPROC-1X-BOOL-ENUM    ::= <V,V|LEN-16> ENUMERATED  
{ 
    cPROC-1X-BOOL-INVALID(0), 
    cPROC-1X-BOOL-VALID(1), 
    cPROC-1X-BOOL-BUTT(2) 
} 

CPROC-1X-RSLT-ENUM    ::= <V,V|LEN-16> ENUMERATED  
{ 
    cPROC-1X-RSLT-SUCC(0), 
    cPROC-1X-RSLT-FAIL(1), 
    cPROC-1X-RSLT-BUTT(2) 
} 

END

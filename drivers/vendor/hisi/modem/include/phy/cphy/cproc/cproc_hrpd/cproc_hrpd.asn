--/*********************************************************************************/
--/* FileName:      cproc_hrpd.asn                                                 */
--/* Description:   H2ASN TOOLS Generate ASN.1 file                                */
--/* CopyRight:     Huawei Technologies Co., Ltd.                                  */
--/* Created By:                                                                   */
--/* HISTORY VER:   NULL                                                           */
--/* VERSION:       1.0                                                            */
--/* Create Time:   2015.6.10 9:54:30                                              */
--/* Create Option: H2ASN C:\Users\j73114\AppData\Local\Temp\Huawei\Daisy\cproc_hrpd.h C:\Users\j73114\AppData\Local\Temp\Huawei\Daisy\cproc_hrpd.asn*/
--/*********************************************************************************/
                                                                                   
--ROOT    : Cproc-hrpd-definitions.Cproc-hrpd-MSG                                              
--PROTOCOL: Cproc-hrpd                                                                     
--ENDIAN  : LITTLE                                                                   
--BOUNDARY: ALIGN                                                                    
--THREAD  : MULTI                                                                    
                                                                                     
Cproc-hrpd-definitions DEFINITIONS ::=                                                             
BEGIN                                                                                
                                                                                   
VOS-UINT8  ::= <V,V|LEN-8>INTEGER(0..255) 

VOS-UINT16 ::= <V,V|LEN-16>INTEGER(0..65535) 

VOS-UINT32 ::= <V,V|LEN-32>INTEGER(0..4294967295) 

VOS-RATMODE-ENUM    ::= <V,V|LEN-32> ENUMERATED  
{ 
    vOS-RATMODE-GSM(0), 
    vOS-RATMODE-WCDMA(1), 
    vOS-RATMODE-LTE(2), 
    vOS-RATMODE-TDS(3), 
    vOS-RATMODE-1X(4), 
    vOS-RATMODE-EVDO(5), 
    vOS-RATMODE-BUTT(6) 
} 

MODEM-ID-ENUM    ::= <V,V|LEN-16> ENUMERATED  
{ 
    mODEM-ID-BUTT(0) 
} 

MsgBlock    ::= <V> SEQUENCE  
{ 
     
    dummy    <V>SEQUENCE(SIZE(4)) OF VOS-UINT8 
} 

CPROC-HRPD-WORKMODE-ENUM    ::= <V,V|LEN-16> ENUMERATED  
{ 
    cPROC-HRPD-WORKMODE-MASTER(0), 
    cPROC-HRPD-WORKMODE-SLAVE(1), 
    cPROC-HRPD-WORKMODE-BUTT(2) 
} 

CPROC-HRPD-CHANNEL-RECORD-STRU    ::= <V> SEQUENCE  
{ 
    usBandClass    VOS-UINT16 , 
 
    usChannelNumber    VOS-UINT16  
} 

END
